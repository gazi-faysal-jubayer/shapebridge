# flange: generated by ShapeBridge (https://github.com/gazi-faysal-jubayer/shapebridge)
# Units: mm. Edit the parameters below; geometry updates from them.

import FreeCAD as App
import Part
import Sketcher
import Draft


def pick_edges(shape, sel):
    """Edge indices (1-based) matching ShapeBridge edge selections."""
    bb = shape.BoundBox
    picked = []
    for i, e in enumerate(shape.Edges, 1):
        zs = [v.Point.z for v in e.Vertexes]
        if sel == "all":
            picked.append(i)
        elif sel == "vertical":
            if isinstance(e.Curve, Part.Line) and abs(abs(e.Curve.Direction.normalize().z) - 1) < 1e-6:
                picked.append(i)
        elif all(abs(z - (bb.ZMax if sel == "top" else bb.ZMin)) < 1e-2 for z in zs):
            picked.append(i)
    return picked


def pick_face(shape, side):
    z = shape.BoundBox.ZMax if side == "top" else shape.BoundBox.ZMin
    for i, f in enumerate(shape.Faces, 1):
        if abs(f.BoundBox.ZMin - z) < 1e-2 and abs(f.BoundBox.ZMax - z) < 1e-2:
            return "Face%d" % i


doc = App.newDocument("flange")
sheet = doc.addObject("Spreadsheet::Sheet", "Params")
sheet.set("A1", "outer_d")
sheet.set("B1", "120")
sheet.setAlias("B1", "outer_d")
sheet.set("A2", "bore_d")
sheet.set("B2", "40")
sheet.setAlias("B2", "bore_d")
sheet.set("A3", "plate")
sheet.set("B3", "12")
sheet.setAlias("B3", "plate")
sheet.set("A4", "hub_d")
sheet.set("B4", "60")
sheet.setAlias("B4", "hub_d")
sheet.set("A5", "hub_h")
sheet.set("B5", "20")
sheet.setAlias("B5", "hub_h")
sheet.set("A6", "bolt_circle")
sheet.set("B6", "45")
sheet.setAlias("B6", "bolt_circle")
sheet.set("A7", "bolts")
sheet.set("B7", "6")
sheet.setAlias("B7", "bolts")
doc.recompute()

# disc
disc_sketch = doc.addObject("Sketcher::SketchObject", "disc_sketch")
disc_sketch.Placement = App.Placement(App.Vector(0, 0, 0), App.Rotation(App.Vector(1, 0, 0), App.Vector(0, 1, 0), App.Vector(0, 0, 1), "ZXY"))
disc_sketch.setExpression("Placement.Base.x", "0")
disc_sketch.setExpression("Placement.Base.y", "0")
disc_sketch.setExpression("Placement.Base.z", "0")
disc_sketch.addGeometry(Part.Circle(App.Vector(0, 0, 0), App.Vector(0, 0, 1), 60))
c = disc_sketch.addConstraint(Sketcher.Constraint("DistanceX", -1, 1, 0, 3, 0))
disc_sketch.setExpression("Constraints[%d]" % c, "0")
c = disc_sketch.addConstraint(Sketcher.Constraint("DistanceY", -1, 1, 0, 3, 0))
disc_sketch.setExpression("Constraints[%d]" % c, "0")  # centre
c = disc_sketch.addConstraint(Sketcher.Constraint("Radius", 0, 60))
disc_sketch.setExpression("Constraints[%d]" % c, "Params.outer_d / 2")
disc = doc.addObject("Part::Extrusion", "disc")
disc.Base = disc_sketch
disc.DirMode = "Normal"
disc.Solid = True
disc.Symmetric = False
disc.Reversed = False
disc.setExpression("LengthFwd", "Params.plate")

# hub
hub_sketch = doc.addObject("Sketcher::SketchObject", "hub_sketch")
hub_sketch.Placement = App.Placement(App.Vector(0, 0, 0), App.Rotation(App.Vector(1, 0, 0), App.Vector(0, 1, 0), App.Vector(0, 0, 1), "ZXY"))
hub_sketch.setExpression("Placement.Base.x", "0")
hub_sketch.setExpression("Placement.Base.y", "0")
hub_sketch.setExpression("Placement.Base.z", "Params.plate")
hub_sketch.addGeometry(Part.Circle(App.Vector(0, 0, 0), App.Vector(0, 0, 1), 30))
c = hub_sketch.addConstraint(Sketcher.Constraint("DistanceX", -1, 1, 0, 3, 0))
hub_sketch.setExpression("Constraints[%d]" % c, "0")
c = hub_sketch.addConstraint(Sketcher.Constraint("DistanceY", -1, 1, 0, 3, 0))
hub_sketch.setExpression("Constraints[%d]" % c, "0")  # centre
c = hub_sketch.addConstraint(Sketcher.Constraint("Radius", 0, 30))
hub_sketch.setExpression("Constraints[%d]" % c, "Params.hub_d / 2")
hub = doc.addObject("Part::Extrusion", "hub")
hub.Base = hub_sketch
hub.DirMode = "Normal"
hub.Solid = True
hub.Symmetric = False
hub.Reversed = False
hub.setExpression("LengthFwd", "Params.hub_h")
fuse_hub = doc.addObject("Part::Fuse", "fuse_hub")
fuse_hub.Base = disc
fuse_hub.Tool = hub

# bore
bore_0 = doc.addObject("Part::Cylinder", "bore_0")
bore_0.Placement = App.Placement(App.Vector(0, 0, 0), App.Rotation(App.Vector(0, 0, 1), App.Vector(0, 0, 1)))
bore_0.setExpression("Radius", "Params.bore_d / 2")
bore_0.setExpression("Height", "Params.plate + Params.hub_h + 0.0001")
bore_0.setExpression("Placement.Base.x", "0")
bore_0.setExpression("Placement.Base.y", "0")
bore_0.setExpression("Placement.Base.z", "Params.plate + Params.hub_h - (Params.plate + Params.hub_h)")
bore = bore_0
cut_bore = doc.addObject("Part::Cut", "cut_bore")
cut_bore.Base = fuse_hub
cut_bore.Tool = bore

# bolt
bolt_0 = doc.addObject("Part::Cylinder", "bolt_0")
bolt_0.Placement = App.Placement(App.Vector(0, 0, 0), App.Rotation(App.Vector(0, 0, 1), App.Vector(0, 0, 1)))
bolt_0.setExpression("Radius", "9 / 2")
bolt_0.setExpression("Height", "Params.plate + 0.0001")
bolt_0.setExpression("Placement.Base.x", "Params.bolt_circle")
bolt_0.setExpression("Placement.Base.y", "0")
bolt_0.setExpression("Placement.Base.z", "Params.plate - Params.plate")
bolt = bolt_0
cut_bolt = doc.addObject("Part::Cut", "cut_bolt")
cut_bolt.Base = cut_bore
cut_bolt.Tool = bolt

# bolt_ring
bolt_ring = Draft.make_polar_array(bolt, number=6, angle=360, center=App.Vector(0, 0, 0), use_link=False)
bolt_ring.setExpression("NumberPolar", "Params.bolts")
bolt_ring.setExpression("Center.x", "0")
bolt_ring.setExpression("Center.y", "0")
cut_bolt_ring = doc.addObject("Part::Cut", "cut_bolt_ring")
cut_bolt_ring.Base = cut_bolt
cut_bolt_ring.Tool = bolt_ring

# edge
doc.recompute()
edge = doc.addObject("Part::Chamfer", "edge")
edge.Base = cut_bolt_ring
edge.Edges = [(i, 1, 1) for i in pick_edges(cut_bolt_ring.Shape, "top")]

edge.Label = "flange"
doc.recompute()
if App.GuiUp:
    import FreeCADGui
    FreeCADGui.SendMsgToActiveView("ViewFit")
