# knob: generated by ShapeBridge (https://github.com/gazi-faysal-jubayer/shapebridge)
# Units: mm. Edit the parameters below; geometry updates from them.

import FreeCAD as App
import Part
import Sketcher
import Draft


def pick_edges(shape, sel):
    """Edge indices (1-based) matching ShapeBridge edge selections."""
    bb = shape.BoundBox
    picked = []
    for i, e in enumerate(shape.Edges, 1):
        zs = [v.Point.z for v in e.Vertexes]
        if sel == "all":
            picked.append(i)
        elif sel == "vertical":
            if isinstance(e.Curve, Part.Line) and abs(abs(e.Curve.Direction.normalize().z) - 1) < 1e-6:
                picked.append(i)
        elif all(abs(z - (bb.ZMax if sel == "top" else bb.ZMin)) < 1e-2 for z in zs):
            picked.append(i)
    return picked


def pick_face(shape, side):
    z = shape.BoundBox.ZMax if side == "top" else shape.BoundBox.ZMin
    for i, f in enumerate(shape.Faces, 1):
        if abs(f.BoundBox.ZMin - z) < 1e-2 and abs(f.BoundBox.ZMax - z) < 1e-2:
            return "Face%d" % i


doc = App.newDocument("knob")
sheet = doc.addObject("Spreadsheet::Sheet", "Params")
sheet.set("A1", "r")
sheet.set("B1", "15")
sheet.setAlias("B1", "r")
sheet.set("A2", "h")
sheet.set("B2", "18")
sheet.setAlias("B2", "p_h")
sheet.set("A3", "grip")
sheet.set("B3", "2")
sheet.setAlias("B3", "grip")
sheet.set("A4", "shaft_d")
sheet.set("B4", "6")
sheet.setAlias("B4", "shaft_d")
doc.recompute()

# body
body_sketch = doc.addObject("Sketcher::SketchObject", "body_sketch")
body_sketch.Placement = App.Placement(App.Vector(0, 0, 0), App.Rotation(App.Vector(1, 0, 0), App.Vector(0, 0, 1), App.Vector(0, -1, 0), "ZXY"))
body_sketch.setExpression("Placement.Base.x", "0")
body_sketch.setExpression("Placement.Base.y", "0")
body_sketch.setExpression("Placement.Base.z", "0")
body_sketch.addGeometry(Part.LineSegment(App.Vector(0, 0, 0), App.Vector(15, 0, 0)))
c = body_sketch.addConstraint(Sketcher.Constraint("DistanceX", -1, 1, 0, 1, 0))
body_sketch.setExpression("Constraints[%d]" % c, "0")
c = body_sketch.addConstraint(Sketcher.Constraint("DistanceY", -1, 1, 0, 1, 0))
body_sketch.setExpression("Constraints[%d]" % c, "0")  # line 0 start
c = body_sketch.addConstraint(Sketcher.Constraint("DistanceX", -1, 1, 0, 2, 15))
body_sketch.setExpression("Constraints[%d]" % c, "Params.r")
c = body_sketch.addConstraint(Sketcher.Constraint("DistanceY", -1, 1, 0, 2, 0))
body_sketch.setExpression("Constraints[%d]" % c, "0")  # line 0 end
body_sketch.addGeometry(Part.LineSegment(App.Vector(15, 0, 0), App.Vector(15, 12.6, 0)))
c = body_sketch.addConstraint(Sketcher.Constraint("DistanceX", -1, 1, 1, 1, 15))
body_sketch.setExpression("Constraints[%d]" % c, "Params.r")
c = body_sketch.addConstraint(Sketcher.Constraint("DistanceY", -1, 1, 1, 1, 0))
body_sketch.setExpression("Constraints[%d]" % c, "0")  # line 1 start
c = body_sketch.addConstraint(Sketcher.Constraint("DistanceX", -1, 1, 1, 2, 15))
body_sketch.setExpression("Constraints[%d]" % c, "Params.r")
c = body_sketch.addConstraint(Sketcher.Constraint("DistanceY", -1, 1, 1, 2, 12.6))
body_sketch.setExpression("Constraints[%d]" % c, "Params.p_h * 0.7")  # line 1 end
body_sketch.addGeometry(Part.LineSegment(App.Vector(15, 12.6, 0), App.Vector(9, 18, 0)))
c = body_sketch.addConstraint(Sketcher.Constraint("DistanceX", -1, 1, 2, 1, 15))
body_sketch.setExpression("Constraints[%d]" % c, "Params.r")
c = body_sketch.addConstraint(Sketcher.Constraint("DistanceY", -1, 1, 2, 1, 12.6))
body_sketch.setExpression("Constraints[%d]" % c, "Params.p_h * 0.7")  # line 2 start
c = body_sketch.addConstraint(Sketcher.Constraint("DistanceX", -1, 1, 2, 2, 9))
body_sketch.setExpression("Constraints[%d]" % c, "Params.r * 0.6")
c = body_sketch.addConstraint(Sketcher.Constraint("DistanceY", -1, 1, 2, 2, 18))
body_sketch.setExpression("Constraints[%d]" % c, "Params.p_h")  # line 2 end
body_sketch.addGeometry(Part.LineSegment(App.Vector(9, 18, 0), App.Vector(0, 18, 0)))
c = body_sketch.addConstraint(Sketcher.Constraint("DistanceX", -1, 1, 3, 1, 9))
body_sketch.setExpression("Constraints[%d]" % c, "Params.r * 0.6")
c = body_sketch.addConstraint(Sketcher.Constraint("DistanceY", -1, 1, 3, 1, 18))
body_sketch.setExpression("Constraints[%d]" % c, "Params.p_h")  # line 3 start
c = body_sketch.addConstraint(Sketcher.Constraint("DistanceX", -1, 1, 3, 2, 0))
body_sketch.setExpression("Constraints[%d]" % c, "0")
c = body_sketch.addConstraint(Sketcher.Constraint("DistanceY", -1, 1, 3, 2, 18))
body_sketch.setExpression("Constraints[%d]" % c, "Params.p_h")  # line 3 end
body_sketch.addGeometry(Part.LineSegment(App.Vector(0, 18, 0), App.Vector(0, 0, 0)))
c = body_sketch.addConstraint(Sketcher.Constraint("DistanceX", -1, 1, 4, 1, 0))
body_sketch.setExpression("Constraints[%d]" % c, "0")
c = body_sketch.addConstraint(Sketcher.Constraint("DistanceY", -1, 1, 4, 1, 18))
body_sketch.setExpression("Constraints[%d]" % c, "Params.p_h")  # line 4 start
c = body_sketch.addConstraint(Sketcher.Constraint("DistanceX", -1, 1, 4, 2, 0))
body_sketch.setExpression("Constraints[%d]" % c, "0")
c = body_sketch.addConstraint(Sketcher.Constraint("DistanceY", -1, 1, 4, 2, 0))
body_sketch.setExpression("Constraints[%d]" % c, "0")  # line 4 end
body = doc.addObject("Part::Revolution", "body")
body.Source = body_sketch
body.Axis = App.Vector(0, 0, 1)
body.setExpression("Base.x", "0")
body.setExpression("Base.y", "0")
body.setExpression("Base.z", "0")
body.Solid = True
body.setExpression("Angle", "360")

# flute
flute_sketch = doc.addObject("Sketcher::SketchObject", "flute_sketch")
flute_sketch.Placement = App.Placement(App.Vector(0, 0, 0), App.Rotation(App.Vector(1, 0, 0), App.Vector(0, 1, 0), App.Vector(0, 0, 1), "ZXY"))
flute_sketch.setExpression("Placement.Base.x", "0")
flute_sketch.setExpression("Placement.Base.y", "0")
flute_sketch.setExpression("Placement.Base.z", "0")
flute_sketch.addGeometry(Part.Circle(App.Vector(15.8, 0, 0), App.Vector(0, 0, 1), 2))
c = flute_sketch.addConstraint(Sketcher.Constraint("DistanceX", -1, 1, 0, 3, 15.8))
flute_sketch.setExpression("Constraints[%d]" % c, "Params.r + Params.grip * 0.4")
c = flute_sketch.addConstraint(Sketcher.Constraint("DistanceY", -1, 1, 0, 3, 0))
flute_sketch.setExpression("Constraints[%d]" % c, "0")  # centre
c = flute_sketch.addConstraint(Sketcher.Constraint("Radius", 0, 2))
flute_sketch.setExpression("Constraints[%d]" % c, "Params.grip")
flute = doc.addObject("Part::Extrusion", "flute")
flute.Base = flute_sketch
flute.DirMode = "Normal"
flute.Solid = True
flute.Symmetric = False
flute.Reversed = False
flute.setExpression("LengthFwd", "Params.p_h * 0.7")
cut_flute = doc.addObject("Part::Cut", "cut_flute")
cut_flute.Base = body
cut_flute.Tool = flute

# flutes
flutes = Draft.make_polar_array(flute, number=12, angle=360, center=App.Vector(0, 0, 0), use_link=False)
flutes.setExpression("NumberPolar", "12")
flutes.setExpression("Center.x", "0")
flutes.setExpression("Center.y", "0")
cut_flutes = doc.addObject("Part::Cut", "cut_flutes")
cut_flutes.Base = cut_flute
cut_flutes.Tool = flutes

# shaft
shaft_0 = doc.addObject("Part::Cylinder", "shaft_0")
shaft_0.Placement = App.Placement(App.Vector(0, 0, 0), App.Rotation(App.Vector(0, 0, 1), App.Vector(0, 0, 1)))
shaft_0.setExpression("Radius", "Params.shaft_d / 2")
shaft_0.setExpression("Height", "Params.p_h * 0.6 + 0.0001")
shaft_0.setExpression("Placement.Base.x", "0")
shaft_0.setExpression("Placement.Base.y", "0")
shaft_0.setExpression("Placement.Base.z", "Params.p_h * 0.6 - Params.p_h * 0.6")
shaft = shaft_0
cut_shaft = doc.addObject("Part::Cut", "cut_shaft")
cut_shaft.Base = cut_flutes
cut_shaft.Tool = shaft

cut_shaft.Label = "knob"
doc.recompute()
if App.GuiUp:
    import FreeCADGui
    FreeCADGui.SendMsgToActiveView("ViewFit")
