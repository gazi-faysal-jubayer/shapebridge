# enclosure: generated by ShapeBridge (https://github.com/gazi-faysal-jubayer/shapebridge)
# Units: mm. Edit the parameters below; geometry updates from them.

import FreeCAD as App
import Part
import Sketcher
import Draft


def pick_edges(shape, sel):
    """Edge indices (1-based) matching ShapeBridge edge selections."""
    bb = shape.BoundBox
    picked = []
    for i, e in enumerate(shape.Edges, 1):
        zs = [v.Point.z for v in e.Vertexes]
        if sel == "all":
            picked.append(i)
        elif sel == "vertical":
            if isinstance(e.Curve, Part.Line) and abs(abs(e.Curve.Direction.normalize().z) - 1) < 1e-6:
                picked.append(i)
        elif all(abs(z - (bb.ZMax if sel == "top" else bb.ZMin)) < 1e-2 for z in zs):
            picked.append(i)
    return picked


def pick_face(shape, side):
    z = shape.BoundBox.ZMax if side == "top" else shape.BoundBox.ZMin
    for i, f in enumerate(shape.Faces, 1):
        if abs(f.BoundBox.ZMin - z) < 1e-2 and abs(f.BoundBox.ZMax - z) < 1e-2:
            return "Face%d" % i


doc = App.newDocument("enclosure")
sheet = doc.addObject("Spreadsheet::Sheet", "Params")
sheet.set("A1", "length")
sheet.set("B1", "100")
sheet.setAlias("B1", "length")
sheet.set("A2", "width")
sheet.set("B2", "60")
sheet.setAlias("B2", "width")
sheet.set("A3", "height")
sheet.set("B3", "35")
sheet.setAlias("B3", "height")
sheet.set("A4", "wall")
sheet.set("B4", "2.5")
sheet.setAlias("B4", "wall")
sheet.set("A5", "radius")
sheet.set("B5", "6")
sheet.setAlias("B5", "radius")
doc.recompute()

# body
body_sketch = doc.addObject("Sketcher::SketchObject", "body_sketch")
body_sketch.Placement = App.Placement(App.Vector(0, 0, 0), App.Rotation(App.Vector(1, 0, 0), App.Vector(0, 1, 0), App.Vector(0, 0, 1), "ZXY"))
body_sketch.setExpression("Placement.Base.x", "0")
body_sketch.setExpression("Placement.Base.y", "0")
body_sketch.setExpression("Placement.Base.z", "0")
body_sketch.addGeometry(Part.LineSegment(App.Vector(0, 0, 0), App.Vector(100, 0, 0)))
c = body_sketch.addConstraint(Sketcher.Constraint("DistanceX", -1, 1, 0, 1, 0))
body_sketch.setExpression("Constraints[%d]" % c, "0")
c = body_sketch.addConstraint(Sketcher.Constraint("DistanceY", -1, 1, 0, 1, 0))
body_sketch.setExpression("Constraints[%d]" % c, "0")  # line 0 start
c = body_sketch.addConstraint(Sketcher.Constraint("DistanceX", -1, 1, 0, 2, 100))
body_sketch.setExpression("Constraints[%d]" % c, "Params.length")
c = body_sketch.addConstraint(Sketcher.Constraint("DistanceY", -1, 1, 0, 2, 0))
body_sketch.setExpression("Constraints[%d]" % c, "0")  # line 0 end
body_sketch.addGeometry(Part.LineSegment(App.Vector(100, 0, 0), App.Vector(100, 60, 0)))
c = body_sketch.addConstraint(Sketcher.Constraint("DistanceX", -1, 1, 1, 1, 100))
body_sketch.setExpression("Constraints[%d]" % c, "Params.length")
c = body_sketch.addConstraint(Sketcher.Constraint("DistanceY", -1, 1, 1, 1, 0))
body_sketch.setExpression("Constraints[%d]" % c, "0")  # line 1 start
c = body_sketch.addConstraint(Sketcher.Constraint("DistanceX", -1, 1, 1, 2, 100))
body_sketch.setExpression("Constraints[%d]" % c, "Params.length")
c = body_sketch.addConstraint(Sketcher.Constraint("DistanceY", -1, 1, 1, 2, 60))
body_sketch.setExpression("Constraints[%d]" % c, "Params.width")  # line 1 end
body_sketch.addGeometry(Part.LineSegment(App.Vector(100, 60, 0), App.Vector(0, 60, 0)))
c = body_sketch.addConstraint(Sketcher.Constraint("DistanceX", -1, 1, 2, 1, 100))
body_sketch.setExpression("Constraints[%d]" % c, "Params.length")
c = body_sketch.addConstraint(Sketcher.Constraint("DistanceY", -1, 1, 2, 1, 60))
body_sketch.setExpression("Constraints[%d]" % c, "Params.width")  # line 2 start
c = body_sketch.addConstraint(Sketcher.Constraint("DistanceX", -1, 1, 2, 2, 0))
body_sketch.setExpression("Constraints[%d]" % c, "0")
c = body_sketch.addConstraint(Sketcher.Constraint("DistanceY", -1, 1, 2, 2, 60))
body_sketch.setExpression("Constraints[%d]" % c, "Params.width")  # line 2 end
body_sketch.addGeometry(Part.LineSegment(App.Vector(0, 60, 0), App.Vector(0, 0, 0)))
c = body_sketch.addConstraint(Sketcher.Constraint("DistanceX", -1, 1, 3, 1, 0))
body_sketch.setExpression("Constraints[%d]" % c, "0")
c = body_sketch.addConstraint(Sketcher.Constraint("DistanceY", -1, 1, 3, 1, 60))
body_sketch.setExpression("Constraints[%d]" % c, "Params.width")  # line 3 start
c = body_sketch.addConstraint(Sketcher.Constraint("DistanceX", -1, 1, 3, 2, 0))
body_sketch.setExpression("Constraints[%d]" % c, "0")
c = body_sketch.addConstraint(Sketcher.Constraint("DistanceY", -1, 1, 3, 2, 0))
body_sketch.setExpression("Constraints[%d]" % c, "0")  # line 3 end
body = doc.addObject("Part::Extrusion", "body")
body.Base = body_sketch
body.DirMode = "Normal"
body.Solid = True
body.Symmetric = False
body.Reversed = False
body.setExpression("LengthFwd", "Params.height")

# round
doc.recompute()
round = doc.addObject("Part::Fillet", "round")
round.Base = body
round.Edges = [(i, 6, 6) for i in pick_edges(body.Shape, "vertical")]

# hollow
doc.recompute()
hollow = doc.addObject("Part::Thickness", "hollow")
hollow.Faces = (round, [pick_face(round.Shape, "top")])
hollow.setExpression("Value", "-Params.wall")  # negative = walls grow inwards
hollow.Join = "Intersection"

hollow.Label = "enclosure"
doc.recompute()
if App.GuiUp:
    import FreeCADGui
    FreeCADGui.SendMsgToActiveView("ViewFit")
